GUDEADS-EPC24X-MIB DEFINITIONS ::= BEGIN

IMPORTS
	enterprises,
	MODULE-IDENTITY,
	OBJECT-TYPE,
	NOTIFICATION-TYPE,
	Counter32,
	Integer32,
	IpAddress,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id: GUDEADS-EPC24X-MIB.txt,v 1.10 2009-04-03 14:03:39 petes1 Exp $"
	-- 1.3.6.1.4.1.28507
	::= { enterprises 28507 }


-- Notification Types
--

events OBJECT IDENTIFIER 
	-- 1.3.6.1.4.1.28507.5.0
	::= { gadsEPC24 0 }

epc24portFuses OBJECT-TYPE
	SYNTAX  Integer32 (0..7)
	MAX-ACCESS read-only
	STATUS  current
	DESCRIPTION
		"Bit State of Fuses (Bit 0 = Fuse1, Bit 1 = Fuse2,
		Bit 2 = Fuse3)

		"
	-- 1.3.6.1.4.1.28507.5.1.2.3
	::= { epc24powerports 3 }


gadsEPC24 OBJECT IDENTIFIER 
	-- 1.3.6.1.4.1.28507.5
	::= { gudeads 5 }

-- Scalars and Tables
--

epc24Objects OBJECT IDENTIFIER 
	-- 1.3.6.1.4.1.28507.5.1
	::= { gadsEPC24 1 }

epc24powerports OBJECT IDENTIFIER 
	-- 1.3.6.1.4.1.28507.5.1.2
	::= { epc24Objects 2 }

epc24portNumber OBJECT-TYPE
	SYNTAX  Integer32 (1..24)
	MAX-ACCESS read-only
	STATUS  current
	DESCRIPTION
		"The number of PowerPorts"
	-- 1.3.6.1.4.1.28507.5.1.2.1
	::= { epc24powerports 1 }


-- the Interfaces table
-- The Interfaces table contains information on the entity's
-- interfaces.  Each sub-layer below the internetwork-layer
-- of a network interface is considered to be an interface.

epc24portTable OBJECT-TYPE
	SYNTAX  SEQUENCE OF Epc24portEntry
	MAX-ACCESS not-accessible
	STATUS  current
	DESCRIPTION
		"list of all EPC Powerports"
	-- 1.3.6.1.4.1.28507.5.1.2.2
	::= { epc24powerports 2 }


epc24portEntry OBJECT-TYPE
	SYNTAX  Epc24portEntry
	MAX-ACCESS not-accessible
	STATUS  current
	DESCRIPTION
		"An entry containing management information applicable to a
		particular powerport."
	INDEX {
		epc24powerPortIndex }
	-- 1.3.6.1.4.1.28507.5.1.2.2.1
	::= { epc24portTable 1 }


Epc24portEntry ::= SEQUENCE {

	epc24powerPortIndex       Integer32,
	epc24powerPortName        OCTET STRING,
	epc24powerPortState       INTEGER,
	epc24powerPortSwitchCount Counter32,
	epc24PortStartupMode      INTEGER,
	epc24PortStartupDelay     Integer32,
	epc24PortRepowerTime      Integer32 }


epc24powerPortIndex OBJECT-TYPE
	SYNTAX  Integer32 (1..24)
	MAX-ACCESS not-accessible
	STATUS  current
	DESCRIPTION
		"A unique value, greater than zero, for each PowerPort."
	-- 1.3.6.1.4.1.28507.5.1.2.2.1.1
	::= { epc24portEntry 1 }


epc24powerPortName OBJECT-TYPE
	SYNTAX  OCTET STRING (SIZE (0..15))
	MAX-ACCESS read-only
	STATUS  current
	DESCRIPTION
		"A textual string containing name of a PowerPort."
	-- 1.3.6.1.4.1.28507.5.1.2.2.1.2
	::= { epc24portEntry 2 }


epc24powerPortState OBJECT-TYPE
	SYNTAX  INTEGER {
			off(0),
			on(1) }
	MAX-ACCESS read-write
	STATUS  current
	DESCRIPTION
		"current state a PowerPort"
	-- 1.3.6.1.4.1.28507.5.1.2.2.1.3
	::= { epc24portEntry 3 }


epc24powerPortSwitchCount OBJECT-TYPE
	SYNTAX  Counter32
	MAX-ACCESS read-only
	STATUS  current
	DESCRIPTION
		"The total number of switch actions ocurred on a PowerPort.
		Does not count switch commands which will not switch
		the ralay state, so just real relay switches are displayed here."
	-- 1.3.6.1.4.1.28507.5.1.2.2.1.4
	::= { epc24portEntry 4 }


-- Conformance
--

epc24Conf OBJECT IDENTIFIER 
	-- 1.3.6.1.4.1.28507.5.3
	::= { gadsEPC24 3 }

-- Groups
--

epc24Groups OBJECT IDENTIFIER 
	-- 1.3.6.1.4.1.28507.5.3.1
	::= { epc24Conf 1 }

-- Compliance
--

epc24Compls OBJECT IDENTIFIER 
	-- 1.3.6.1.4.1.28507.5.3.2
	::= { epc24Conf 2 }

epc24SNMPaccess OBJECT IDENTIFIER 
	-- 1.3.6.1.4.1.28507.5.1.1
	::= { epc24Objects 1 }

epc24TrapCtrl OBJECT-TYPE
	SYNTAX  Integer32 (0..2)
	MAX-ACCESS read-write
	STATUS  current
	DESCRIPTION
		"0 = off
		1 = Ver. 1
		2 = Ver. 2c"
	-- 1.3.6.1.4.1.28507.5.1.1.1
	::= { epc24SNMPaccess 1 }


epc24TrapIPTable OBJECT-TYPE
	SYNTAX  SEQUENCE OF Epc24TrapIPEntry
	MAX-ACCESS not-accessible
	STATUS  current
	DESCRIPTION
		"list of all Trap receiver"
	-- 1.3.6.1.4.1.28507.5.1.1.2
	::= { epc24SNMPaccess 2 }


epc24TrapIPEntry OBJECT-TYPE
	SYNTAX  Epc24TrapIPEntry
	MAX-ACCESS not-accessible
	STATUS  current
	DESCRIPTION
		"an entry containing management
		informations regarding the list of trap
		receivers"
	INDEX {
		epc24TrapIPIndex }
	-- 1.3.6.1.4.1.28507.5.1.1.2.1
	::= { epc24TrapIPTable 1 }


Epc24TrapIPEntry ::= SEQUENCE {

	epc24TrapIPIndex Integer32,
	epc24TrapIPAddr  IpAddress,
	epc24TrapIPPort  Integer32 }


epc24TrapIPIndex OBJECT-TYPE
	SYNTAX  Integer32 (1..8)
	MAX-ACCESS not-accessible
	STATUS  current
	DESCRIPTION
		"A unique value, greater than zero, for each receiver slot."
	-- 1.3.6.1.4.1.28507.5.1.1.2.1.1
	::= { epc24TrapIPEntry 1 }


epc24TrapIPPort OBJECT-TYPE
	SYNTAX  Integer32 (0..1024)
	MAX-ACCESS read-write
	STATUS  current
	DESCRIPTION
		"IP Port specifying one Trap receiver slot.
		A value of  0 disables this slot."
	DEFVAL { 162 }
	-- 1.3.6.1.4.1.28507.5.1.1.2.1.3
	::= { epc24TrapIPEntry 3 }


epc24TrapIPAddr OBJECT-TYPE
	SYNTAX  IpAddress
	MAX-ACCESS read-write
	STATUS  current
	DESCRIPTION
		"IP Address specifying one Trap receiver slot.
		A value of '00000000'H disables this slot."
	DEFVAL { '00000000'H }
	-- 1.3.6.1.4.1.28507.5.1.1.2.1.2
	::= { epc24TrapIPEntry 2 }


epc24PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.5.1.2.2.1.5
	::= { epc24portEntry 5 }


epc24PortStartupDelay OBJECT-TYPE
	SYNTAX  Integer32
	UNITS
		"seconds"
	MAX-ACCESS read-write
	STATUS  current
	DESCRIPTION
		"Delay in sec for startup action"
	DEFVAL { 0 }
	-- 1.3.6.1.4.1.28507.5.1.2.2.1.6
	::= { epc24portEntry 6 }


epc24PortRepowerTime OBJECT-TYPE
	SYNTAX  Integer32 (0..65535)
	UNITS
		"seconds"
	MAX-ACCESS read-write
	STATUS  current
	DESCRIPTION
		"Delay in sec for repower port after switching off"
	DEFVAL { 0 }
	-- 1.3.6.1.4.1.28507.5.1.2.2.1.7
	::= { epc24portEntry 7 }


epc24powerTable OBJECT-TYPE
	SYNTAX  SEQUENCE OF Epc24powerEntry
	MAX-ACCESS not-accessible
	STATUS  current
	DESCRIPTION
		""
	-- 1.3.6.1.4.1.28507.5.1.2.4
	::= { epc24powerports 4 }


epc24powerEntry OBJECT-TYPE
	SYNTAX  Epc24powerEntry
	MAX-ACCESS not-accessible
	STATUS  current
	DESCRIPTION
		""
	INDEX {
		epc24bankIndex }
	-- 1.3.6.1.4.1.28507.5.1.2.4.1
	::= { epc24powerTable 1 }


Epc24powerEntry ::= SEQUENCE {

	epc24bankIndex   Integer32,
	epc24bankCurrent Unsigned32,
	epc24bankVoltage Unsigned32 }


epc24bankIndex OBJECT-TYPE
	SYNTAX  Integer32 (1..3)
	MAX-ACCESS not-accessible
	STATUS  current
	DESCRIPTION
		""
	-- 1.3.6.1.4.1.28507.5.1.2.4.1.1
	::= { epc24powerEntry 1 }


epc24bankCurrent OBJECT-TYPE
	SYNTAX  Unsigned32
	UNITS
		"mili Ampere"
	MAX-ACCESS read-only
	STATUS  current
	DESCRIPTION
		"Actual Current on Bank 1..3"
	-- 1.3.6.1.4.1.28507.5.1.2.4.1.2
	::= { epc24powerEntry 2 }


epc24bankVoltage OBJECT-TYPE
	SYNTAX  Unsigned32
	UNITS
		"Volt"
	MAX-ACCESS read-only
	STATUS  current
	DESCRIPTION
		"Actual Voltage on Bank 1..3"
	-- 1.3.6.1.4.1.28507.5.1.2.4.1.3
	::= { epc24powerEntry 3 }



epc24SwitchEvtPort1 NOTIFICATION-TYPE
	OBJECTS {
		epc24powerPortName,
		epc24powerPortState,
		epc24powerPortSwitchCount}
	STATUS  current
	DESCRIPTION
		"Event is triggered when a power port is
		switched"
	-- 1.3.6.1.4.1.28507.5.0.1
	::= { events 1 }


epc24SwitchEvtPort2 NOTIFICATION-TYPE
	OBJECTS {
		epc24powerPortName,
		epc24powerPortState,
		epc24powerPortSwitchCount}
	STATUS  current
	DESCRIPTION
		"Event is triggered when a power port is
		switched"
	-- 1.3.6.1.4.1.28507.5.0.2
	::= { events 2 }


epc24SwitchEvtPort3 NOTIFICATION-TYPE
	OBJECTS {
		epc24powerPortName,
		epc24powerPortState,
		epc24powerPortSwitchCount}
	STATUS  current
	DESCRIPTION
		"Event is triggered when a power port is
		switched"
	-- 1.3.6.1.4.1.28507.5.0.3
	::= { events 3 }


epc24SwitchEvtPort4 NOTIFICATION-TYPE
	OBJECTS {
		epc24powerPortName,
		epc24powerPortState,
		epc24powerPortSwitchCount}
	STATUS  current
	DESCRIPTION
		"Event is triggered when a power port is
		switched"
	-- 1.3.6.1.4.1.28507.5.0.4
	::= { events 4 }


epc24SwitchEvtPort5 NOTIFICATION-TYPE
	OBJECTS {
		epc24powerPortName,
		epc24powerPortState,
		epc24powerPortSwitchCount}
	STATUS  current
	DESCRIPTION
		"Event is triggered when a power port is
		switched"
	-- 1.3.6.1.4.1.28507.5.0.5
	::= { events 5 }


epc24SwitchEvtPort6 NOTIFICATION-TYPE
	OBJECTS {
		epc24powerPortName,
		epc24powerPortState,
		epc24powerPortSwitchCount}
	STATUS  current
	DESCRIPTION
		"Event is triggered when a power port is
		switched"
	-- 1.3.6.1.4.1.28507.5.0.6
	::= { events 6 }


epc24SwitchEvtPort7 NOTIFICATION-TYPE
	OBJECTS {
		epc24powerPortName,
		epc24powerPortState,
		epc24powerPortSwitchCount}
	STATUS  current
	DESCRIPTION
		"Event is triggered when a power port is
		switched"
	-- 1.3.6.1.4.1.28507.5.0.7
	::= { events 7 }


epc24SwitchEvtPort8 NOTIFICATION-TYPE
	OBJECTS {
		epc24powerPortName,
		epc24powerPortState,
		epc24powerPortSwitchCount}
	STATUS  current
	DESCRIPTION
		"Event is triggered when a power port is
		switched"
	-- 1.3.6.1.4.1.28507.5.0.8
	::= { events 8 }


epc24SwitchEvtPort9 NOTIFICATION-TYPE
	OBJECTS {
		epc24powerPortName,
		epc24powerPortState,
		epc24powerPortSwitchCount}
	STATUS  current
	DESCRIPTION
		"Event is triggered when a power port is
		switched"
	-- 1.3.6.1.4.1.28507.5.0.9
	::= { events 9 }


epc24SwitchEvtPort10 NOTIFICATION-TYPE
	OBJECTS {
		epc24powerPortName,
		epc24powerPortState,
		epc24powerPortSwitchCount}
	STATUS  current
	DESCRIPTION
		"Event is triggered when a power port is
		switched"
	-- 1.3.6.1.4.1.28507.5.0.10
	::= { events 10 }


epc24SwitchEvtPort11 NOTIFICATION-TYPE
	OBJECTS {
		epc24powerPortName,
		epc24powerPortState,
		epc24powerPortSwitchCount}
	STATUS  current
	DESCRIPTION
		"Event is triggered when a power port is
		switched"
	-- 1.3.6.1.4.1.28507.5.0.11
	::= { events 11 }


epc24SwitchEvtPort12 NOTIFICATION-TYPE
	OBJECTS {
		epc24powerPortName,
		epc24powerPortState,
		epc24powerPortSwitchCount}
	STATUS  current
	DESCRIPTION
		"Event is triggered when a power port is
		switched"
	-- 1.3.6.1.4.1.28507.5.0.12
	::= { events 12 }


epc24SwitchEvtPort13 NOTIFICATION-TYPE
	OBJECTS {
		epc24powerPortName,
		epc24powerPortState,
		epc24powerPortSwitchCount}
	STATUS  current
	DESCRIPTION
		"Event is triggered when a power port is
		switched"
	-- 1.3.6.1.4.1.28507.5.0.13
	::= { events 13 }


epc24SwitchEvtPort14 NOTIFICATION-TYPE
	OBJECTS {
		epc24powerPortName,
		epc24powerPortState,
		epc24powerPortSwitchCount}
	STATUS  current
	DESCRIPTION
		"Event is triggered when a power port is
		switched"
	-- 1.3.6.1.4.1.28507.5.0.14
	::= { events 14 }


epc24SwitchEvtPort15 NOTIFICATION-TYPE
	OBJECTS {
		epc24powerPortName,
		epc24powerPortState,
		epc24powerPortSwitchCount}
	STATUS  current
	DESCRIPTION
		"Event is triggered when a power port is
		switched"
	-- 1.3.6.1.4.1.28507.5.0.15
	::= { events 15 }


epc24SwitchEvtPort16 NOTIFICATION-TYPE
	OBJECTS {
		epc24powerPortName,
		epc24powerPortState,
		epc24powerPortSwitchCount}
	STATUS  current
	DESCRIPTION
		"Event is triggered when a power port is
		switched"
	-- 1.3.6.1.4.1.28507.5.0.16
	::= { events 16 }


epc24SwitchEvtPort17 NOTIFICATION-TYPE
	OBJECTS {
		epc24powerPortName,
		epc24powerPortState,
		epc24powerPortSwitchCount}
	STATUS  current
	DESCRIPTION
		"Event is triggered when a power port is
		switched"
	-- 1.3.6.1.4.1.28507.5.0.17
	::= { events 17 }


epc24SwitchEvtPort18 NOTIFICATION-TYPE
	OBJECTS {
		epc24powerPortName,
		epc24powerPortState,
		epc24powerPortSwitchCount}
	STATUS  current
	DESCRIPTION
		"Event is triggered when a power port is
		switched"
	-- 1.3.6.1.4.1.28507.5.0.18
	::= { events 18 }


epc24SwitchEvtPort19 NOTIFICATION-TYPE
	OBJECTS {
		epc24powerPortName,
		epc24powerPortState,
		epc24powerPortSwitchCount}
	STATUS  current
	DESCRIPTION
		"Event is triggered when a power port is
		switched"
	-- 1.3.6.1.4.1.28507.5.0.19
	::= { events 19 }


epc24SwitchEvtPort20 NOTIFICATION-TYPE
	OBJECTS {
		epc24powerPortName,
		epc24powerPortState,
		epc24powerPortSwitchCount}
	STATUS  current
	DESCRIPTION
		"Event is triggered when a power port is
		switched"
	-- 1.3.6.1.4.1.28507.5.0.20
	::= { events 20 }


epc24SwitchEvtPort21 NOTIFICATION-TYPE
	OBJECTS {
		epc24powerPortName,
		epc24powerPortState,
		epc24powerPortSwitchCount}
	STATUS  current
	DESCRIPTION
		"Event is triggered when a power port is
		switched"
	-- 1.3.6.1.4.1.28507.5.0.21
	::= { events 21 }


epc24SwitchEvtPort22 NOTIFICATION-TYPE
	OBJECTS {
		epc24powerPortName,
		epc24powerPortState,
		epc24powerPortSwitchCount}
	STATUS  current
	DESCRIPTION
		"Event is triggered when a power port is
		switched"
	-- 1.3.6.1.4.1.28507.5.0.22
	::= { events 22 }


epc24SwitchEvtPort23 NOTIFICATION-TYPE
	OBJECTS {
		epc24powerPortName,
		epc24powerPortState,
		epc24powerPortSwitchCount}
	STATUS  current
	DESCRIPTION
		"Event is triggered when a power port is
		switched"
	-- 1.3.6.1.4.1.28507.5.0.23
	::= { events 23 }


epc24SwitchEvtPort24 NOTIFICATION-TYPE
	OBJECTS {
		epc24powerPortName,
		epc24powerPortState,
		epc24powerPortSwitchCount}
	STATUS  current
	DESCRIPTION
		"Event is triggered when a power port is
		switched"
	-- 1.3.6.1.4.1.28507.5.0.24
	::= { events 24 }


epc24FuseEvt NOTIFICATION-TYPE
	OBJECTS {
		epc24portFuses}
	STATUS  current
	DESCRIPTION
		"Event is triggered when Fuse is blown or reset"
	-- 1.3.6.1.4.1.28507.5.0.25
	::= { events 25 }

epc24BasicGroup OBJECT-GROUP
	OBJECTS {
		epc24portNumber,
		epc24powerPortName,
		epc24powerPortState,
		epc24powerPortSwitchCount,
		epc24portFuses,
		epc24TrapCtrl,
		epc24TrapIPAddr,
		epc24TrapIPPort,
		epc24bankCurrent,
		epc24bankVoltage,
		epc24PortStartupMode,
		epc24PortStartupDelay,
		epc24PortRepowerTime }
	STATUS  current
	DESCRIPTION
		"Basic objects."
	-- 1.3.6.1.4.1.28507.5.3.1.1
	::= { epc24Groups 1 }

epc24NotificationGroup NOTIFICATION-GROUP
	NOTIFICATIONS {
		epc24SwitchEvtPort1,
		epc24FuseEvt,
		epc24SwitchEvtPort2,
		epc24SwitchEvtPort3,
		epc24SwitchEvtPort4,
		epc24SwitchEvtPort5,
		epc24SwitchEvtPort6,
		epc24SwitchEvtPort7,
		epc24SwitchEvtPort8,
		epc24SwitchEvtPort9,
		epc24SwitchEvtPort10,
		epc24SwitchEvtPort11,
		epc24SwitchEvtPort12,
		epc24SwitchEvtPort13,
		epc24SwitchEvtPort14,
		epc24SwitchEvtPort15,
		epc24SwitchEvtPort16,
		epc24SwitchEvtPort17,
		epc24SwitchEvtPort18,
		epc24SwitchEvtPort19,
		epc24SwitchEvtPort20,
		epc24SwitchEvtPort21,
		epc24SwitchEvtPort22,
		epc24SwitchEvtPort23,
		epc24SwitchEvtPort24 }
	STATUS  current
	DESCRIPTION
		""
	-- 1.3.6.1.4.1.28507.5.3.1.2
	::= { epc24Groups 2 }

END
