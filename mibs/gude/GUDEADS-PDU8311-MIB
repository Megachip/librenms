GUDEADS-PDU8311-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "201904041600Z"	-- Apr 4, 2019, 4:00:00 PM
	ORGANIZATION "GUDE Systems GmbH"
	CONTACT-INFO
		"Von-der-Wettern-Str. 23
		51149 Cologne
		Germany
		https://www.gude.info"
	DESCRIPTION
		"Expert PDU Energy 8311 MIB"
	REVISION "201904041600Z"	-- Apr 4, 2019, 4:00:00 PM
	DESCRIPTION
		""
	-- 1.3.6.1.4.1.28507
	::= { enterprises 28507 }


pdu8311LineSensorName OBJECT-TYPE
	SYNTAX  OCTET STRING (SIZE (0..32))
	MAX-ACCESS read-write
	STATUS  current
	DESCRIPTION
		"A textual string containing name of a
		Line Sensor"
	-- 1.3.6.1.4.1.28507.62.1.5.1.2.1.100
	::= { pdu8311PowerEntry 100 }


pdu8311ExtSensorName OBJECT-TYPE
	SYNTAX  OCTET STRING (SIZE (0..32))
	MAX-ACCESS read-write
	STATUS  current
	DESCRIPTION
		"A textual string containing name of a
		external Sensor"
	-- 1.3.6.1.4.1.28507.62.1.6.1.1.32
	::= { pdu8311SensorEntry 32 }



pdu8311AirPressureEvtSen NOTIFICATION-TYPE
	OBJECTS {
		pdu8311SensorIndex,
		pdu8311AirPressure}
	STATUS  current
	DESCRIPTION
		"Air Pressure limits exceeded

		"
	-- 1.3.6.1.4.1.28507.62.3.4
	::= { events 4 }


pdu8311DewPtDiffEvtSen NOTIFICATION-TYPE
	OBJECTS {
		pdu8311SensorIndex,
		pdu8311DewPointDiff}
	STATUS  current
	DESCRIPTION
		"Dew Point Difference limits exceeded"
	-- 1.3.6.1.4.1.28507.62.3.5
	::= { events 5 }

gadsPDU8311 OBJECT IDENTIFIER 
	-- 1.3.6.1.4.1.28507.62
	::= { gudeads 62 }

-- Notification Types
--

events OBJECT IDENTIFIER 
	-- 1.3.6.1.4.1.28507.62.3
	::= { gadsPDU8311 3 }

-- Scalars and Tables
--

pdu8311Objects OBJECT IDENTIFIER 
	-- 1.3.6.1.4.1.28507.62.1
	::= { gadsPDU8311 1 }

pdu8311CommonConfig OBJECT IDENTIFIER 
	-- 1.3.6.1.4.1.28507.62.1.1
	::= { pdu8311Objects 1 }

pdu8311SNMPaccess OBJECT IDENTIFIER 
	-- 1.3.6.1.4.1.28507.62.1.1.1
	::= { pdu8311CommonConfig 1 }

pdu8311TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.62.1.1.1.1
	::= { pdu8311SNMPaccess 1 }


pdu8311TrapIPTable OBJECT-TYPE
	SYNTAX  SEQUENCE OF Pdu8311TrapIPEntry
	MAX-ACCESS not-accessible
	STATUS  current
	DESCRIPTION
		"list of all Trap receiver"
	-- 1.3.6.1.4.1.28507.62.1.1.1.2
	::= { pdu8311SNMPaccess 2 }


pdu8311TrapIPEntry OBJECT-TYPE
	SYNTAX  Pdu8311TrapIPEntry
	MAX-ACCESS not-accessible
	STATUS  current
	DESCRIPTION
		"an entry containing management
		informations regarding the list of trap
		receivers"
	INDEX {
		pdu8311TrapIPIndex }
	-- 1.3.6.1.4.1.28507.62.1.1.1.2.1
	::= { pdu8311TrapIPTable 1 }


Pdu8311TrapIPEntry ::= SEQUENCE {

	pdu8311TrapIPIndex Integer32,
	pdu8311TrapAddr    OCTET STRING }


pdu8311TrapIPIndex OBJECT-TYPE
	SYNTAX  Integer32 (1..8)
	MAX-ACCESS read-only
	STATUS  current
	DESCRIPTION
		"A unique value, greater than zero, for each receiver slot."
	-- 1.3.6.1.4.1.28507.62.1.1.1.2.1.1
	::= { pdu8311TrapIPEntry 1 }


pdu8311TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.62.1.1.1.2.1.2
	::= { pdu8311TrapIPEntry 2 }


pdu8311DeviceConfig OBJECT IDENTIFIER 
	-- 1.3.6.1.4.1.28507.62.1.2
	::= { pdu8311Objects 2 }

pdu8311IntActors OBJECT IDENTIFIER 
	-- 1.3.6.1.4.1.28507.62.1.3
	::= { pdu8311Objects 3 }

pdu8311ExtActors OBJECT IDENTIFIER 
	-- 1.3.6.1.4.1.28507.62.1.4
	::= { pdu8311Objects 4 }

pdu8311IntSensors OBJECT IDENTIFIER 
	-- 1.3.6.1.4.1.28507.62.1.5
	::= { pdu8311Objects 5 }

pdu8311PowerChan OBJECT IDENTIFIER 
	-- 1.3.6.1.4.1.28507.62.1.5.1
	::= { pdu8311IntSensors 1 }

pdu8311ActivePowerChan OBJECT-TYPE
	SYNTAX  Unsigned32 (1..3)
	MAX-ACCESS read-only
	STATUS  current
	DESCRIPTION
		"Number of suppported Power Channels."
	-- 1.3.6.1.4.1.28507.62.1.5.1.1
	::= { pdu8311PowerChan 1 }


pdu8311PowerTable OBJECT-TYPE
	SYNTAX  SEQUENCE OF Pdu8311PowerEntry
	MAX-ACCESS not-accessible
	STATUS  current
	DESCRIPTION
		"All available Channel Interfaces."
	-- 1.3.6.1.4.1.28507.62.1.5.1.2
	::= { pdu8311PowerChan 2 }


pdu8311PowerEntry OBJECT-TYPE
	SYNTAX  Pdu8311PowerEntry
	MAX-ACCESS not-accessible
	STATUS  current
	DESCRIPTION
		"An entry containing management information
		applicable to a particular Power Channel."
	INDEX {
		pdu8311PowerIndex }
	-- 1.3.6.1.4.1.28507.62.1.5.1.2.1
	::= { pdu8311PowerTable 1 }


Pdu8311PowerEntry ::= SEQUENCE {

	pdu8311PowerIndex                   Integer32,
	pdu8311ChanStatus                   Integer32,
	pdu8311AbsEnergyActive              Unsigned32,
	pdu8311PowerActive                  Integer32,
	pdu8311Current                      Unsigned32,
	pdu8311Voltage                      Unsigned32,
	pdu8311Frequency                    Unsigned32,
	pdu8311PowerFactor                  Integer32,
	pdu8311Pangle                       Integer32,
	pdu8311PowerApparent                Integer32,
	pdu8311PowerReactive                Integer32,
	pdu8311AbsEnergyReactive            Unsigned32,
	pdu8311AbsEnergyActiveResettable    Unsigned32,
	pdu8311AbsEnergyReactiveResettable  Unsigned32,
	pdu8311ResetTime                    Unsigned32,
	pdu8311ForwEnergyActive             Unsigned32,
	pdu8311ForwEnergyReactive           Unsigned32,
	pdu8311ForwEnergyActiveResettable   Unsigned32,
	pdu8311ForwEnergyReactiveResettable Unsigned32,
	pdu8311RevEnergyActive              Unsigned32,
	pdu8311RevEnergyReactive            Unsigned32,
	pdu8311RevEnergyActiveResettable    Unsigned32,
	pdu8311RevEnergyReactiveResettable  Unsigned32,
	pdu8311ResidualCurrent              Unsigned32,
	pdu8311LineSensorName               OCTET STRING }


pdu8311PowerIndex OBJECT-TYPE
	SYNTAX  Integer32 (1)
	MAX-ACCESS read-only
	STATUS  current
	DESCRIPTION
		"Index of Power Channel entries"
	-- 1.3.6.1.4.1.28507.62.1.5.1.2.1.1
	::= { pdu8311PowerEntry 1 }


pdu8311ChanStatus OBJECT-TYPE
	SYNTAX  Integer32 (0..1)
	MAX-ACCESS read-only
	STATUS  current
	DESCRIPTION
		"0 = data not active, 1 = data valid"
	-- 1.3.6.1.4.1.28507.62.1.5.1.2.1.2
	::= { pdu8311PowerEntry 2 }


pdu8311AbsEnergyActive OBJECT-TYPE
	SYNTAX  Unsigned32
	UNITS	"Wh"
	MAX-ACCESS read-only
	STATUS  current
	DESCRIPTION
		"Absolute Active Energy counter."
	-- 1.3.6.1.4.1.28507.62.1.5.1.2.1.3
	::= { pdu8311PowerEntry 3 }


pdu8311PowerActive OBJECT-TYPE
	SYNTAX  Integer32
	UNITS	"W"
	MAX-ACCESS read-only
	STATUS  current
	DESCRIPTION
		"Active Power"
	-- 1.3.6.1.4.1.28507.62.1.5.1.2.1.4
	::= { pdu8311PowerEntry 4 }


pdu8311Current OBJECT-TYPE
	SYNTAX  Unsigned32
	UNITS	"mA"
	MAX-ACCESS read-only
	STATUS  current
	DESCRIPTION
		"Actual Current on Power Channel."
	-- 1.3.6.1.4.1.28507.62.1.5.1.2.1.5
	::= { pdu8311PowerEntry 5 }


pdu8311ResidualCurrent OBJECT-TYPE
	SYNTAX  Unsigned32
	UNITS	"mA"
	MAX-ACCESS read-only
	STATUS  current
	DESCRIPTION
		"Actual Residual Current on Power Channel.
		According Typ A IEC 60755. Only visible on
		models that support this feature."
	-- 1.3.6.1.4.1.28507.62.1.5.1.2.1.24
	::= { pdu8311PowerEntry 24 }


pdu8311Voltage OBJECT-TYPE
	SYNTAX  Unsigned32
	UNITS	"V"
	MAX-ACCESS read-only
	STATUS  current
	DESCRIPTION
		"Actual Voltage on Power Channel"
	-- 1.3.6.1.4.1.28507.62.1.5.1.2.1.6
	::= { pdu8311PowerEntry 6 }


pdu8311Frequency OBJECT-TYPE
	SYNTAX  Unsigned32
	UNITS	"0.01 hz"
	MAX-ACCESS read-only
	STATUS  current
	DESCRIPTION
		"Frequency of Power Channel"
	-- 1.3.6.1.4.1.28507.62.1.5.1.2.1.7
	::= { pdu8311PowerEntry 7 }


pdu8311PowerFactor OBJECT-TYPE
	SYNTAX  Integer32
	UNITS	"0.001"
	MAX-ACCESS read-only
	STATUS  current
	DESCRIPTION
		"Power Factor of Channel between
		-1.0 and 1.00"
	-- 1.3.6.1.4.1.28507.62.1.5.1.2.1.8
	::= { pdu8311PowerEntry 8 }


pdu8311Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.62.1.5.1.2.1.9
	::= { pdu8311PowerEntry 9 }


pdu8311PowerApparent OBJECT-TYPE
	SYNTAX  Integer32
	UNITS	"VA"
	MAX-ACCESS read-only
	STATUS  current
	DESCRIPTION
		"L Line Mean Apparent Power"
	-- 1.3.6.1.4.1.28507.62.1.5.1.2.1.10
	::= { pdu8311PowerEntry 10 }


pdu8311PowerReactive OBJECT-TYPE
	SYNTAX  Integer32
	UNITS	"VAR"
	MAX-ACCESS read-only
	STATUS  current
	DESCRIPTION
		"L Line Mean Reactive Power"
	-- 1.3.6.1.4.1.28507.62.1.5.1.2.1.11
	::= { pdu8311PowerEntry 11 }


pdu8311AbsEnergyReactive OBJECT-TYPE
	SYNTAX  Unsigned32
	UNITS	"VARh"
	MAX-ACCESS read-only
	STATUS  current
	DESCRIPTION
		"Absolute Reactive Energy counter."
	-- 1.3.6.1.4.1.28507.62.1.5.1.2.1.12
	::= { pdu8311PowerEntry 12 }


pdu8311AbsEnergyActiveResettable OBJECT-TYPE
	SYNTAX  Unsigned32
	UNITS	"Wh"
	MAX-ACCESS read-write
	STATUS  current
	DESCRIPTION
		"Resettable Absolute Active Energy counter.
		Writing '0' resets all resettable counter."
	-- 1.3.6.1.4.1.28507.62.1.5.1.2.1.13
	::= { pdu8311PowerEntry 13 }


pdu8311AbsEnergyReactiveResettable OBJECT-TYPE
	SYNTAX  Unsigned32
	UNITS	"VARh"
	MAX-ACCESS read-only
	STATUS  current
	DESCRIPTION
		"Resettable Absolute Reactive Energy counter."
	-- 1.3.6.1.4.1.28507.62.1.5.1.2.1.14
	::= { pdu8311PowerEntry 14 }


pdu8311ResetTime OBJECT-TYPE
	SYNTAX  Unsigned32
	UNITS	"s"
	MAX-ACCESS read-only
	STATUS  current
	DESCRIPTION
		"Time in seconds since last Energy
		Counter reset."
	-- 1.3.6.1.4.1.28507.62.1.5.1.2.1.15
	::= { pdu8311PowerEntry 15 }


pdu8311ForwEnergyActive OBJECT-TYPE
	SYNTAX  Unsigned32
	UNITS	"Wh"
	MAX-ACCESS read-only
	STATUS  current
	DESCRIPTION
		"Forward Active Energy counter."
	-- 1.3.6.1.4.1.28507.62.1.5.1.2.1.16
	::= { pdu8311PowerEntry 16 }


pdu8311ForwEnergyReactive OBJECT-TYPE
	SYNTAX  Unsigned32
	UNITS	"VARh"
	MAX-ACCESS read-only
	STATUS  current
	DESCRIPTION
		"Forward Reactive Energy counter."
	-- 1.3.6.1.4.1.28507.62.1.5.1.2.1.17
	::= { pdu8311PowerEntry 17 }


pdu8311ForwEnergyActiveResettable OBJECT-TYPE
	SYNTAX  Unsigned32
	UNITS	"Wh"
	MAX-ACCESS read-only
	STATUS  current
	DESCRIPTION
		"Resettable Forward Active Energy counter."
	-- 1.3.6.1.4.1.28507.62.1.5.1.2.1.18
	::= { pdu8311PowerEntry 18 }


pdu8311ForwEnergyReactiveResettable OBJECT-TYPE
	SYNTAX  Unsigned32
	UNITS	"VARh"
	MAX-ACCESS read-only
	STATUS  current
	DESCRIPTION
		"Resettable Forward Reactive Energy counter."
	-- 1.3.6.1.4.1.28507.62.1.5.1.2.1.19
	::= { pdu8311PowerEntry 19 }


pdu8311RevEnergyActive OBJECT-TYPE
	SYNTAX  Unsigned32
	UNITS	"Wh"
	MAX-ACCESS read-only
	STATUS  current
	DESCRIPTION
		"Reverse Active Energy counter."
	-- 1.3.6.1.4.1.28507.62.1.5.1.2.1.20
	::= { pdu8311PowerEntry 20 }


pdu8311RevEnergyReactive OBJECT-TYPE
	SYNTAX  Unsigned32
	UNITS	"VARh"
	MAX-ACCESS read-only
	STATUS  current
	DESCRIPTION
		"Reverse Reactive Energy counter."
	-- 1.3.6.1.4.1.28507.62.1.5.1.2.1.21
	::= { pdu8311PowerEntry 21 }


pdu8311RevEnergyActiveResettable OBJECT-TYPE
	SYNTAX  Unsigned32
	UNITS	"Wh"
	MAX-ACCESS read-only
	STATUS  current
	DESCRIPTION
		"Resettable Reverse Active Energy counter."
	-- 1.3.6.1.4.1.28507.62.1.5.1.2.1.22
	::= { pdu8311PowerEntry 22 }


pdu8311RevEnergyReactiveResettable OBJECT-TYPE
	SYNTAX  Unsigned32
	UNITS	"VARh"
	MAX-ACCESS read-only
	STATUS  current
	DESCRIPTION
		"Resettable Reverse Reactive Energy counter."
	-- 1.3.6.1.4.1.28507.62.1.5.1.2.1.23
	::= { pdu8311PowerEntry 23 }


pdu8311ExtSensors OBJECT IDENTIFIER 
	-- 1.3.6.1.4.1.28507.62.1.6
	::= { pdu8311Objects 6 }

pdu8311SensorTable OBJECT-TYPE
	SYNTAX  SEQUENCE OF Pdu8311SensorEntry
	MAX-ACCESS not-accessible
	STATUS  current
	DESCRIPTION ""
	-- 1.3.6.1.4.1.28507.62.1.6.1
	::= { pdu8311ExtSensors 1 }


pdu8311SensorEntry OBJECT-TYPE
	SYNTAX  Pdu8311SensorEntry
	MAX-ACCESS not-accessible
	STATUS  current
	DESCRIPTION ""
	INDEX {
		pdu8311SensorIndex }
	-- 1.3.6.1.4.1.28507.62.1.6.1.1
	::= { pdu8311SensorTable 1 }


Pdu8311SensorEntry ::= SEQUENCE {

	pdu8311SensorIndex   Integer32,
	pdu8311TempSensor    Integer32,
	pdu8311HygroSensor   Integer32,
	pdu8311InputSensor   INTEGER,
	pdu8311AirPressure   Integer32,
	pdu8311DewPoint      Integer32,
	pdu8311DewPointDiff  Integer32,
	pdu8311ExtSensorName OCTET STRING }


pdu8311SensorIndex OBJECT-TYPE
	SYNTAX  Integer32 (1..2)
	MAX-ACCESS read-only
	STATUS  current
	DESCRIPTION ""
	-- 1.3.6.1.4.1.28507.62.1.6.1.1.1
	::= { pdu8311SensorEntry 1 }


pdu8311TempSensor OBJECT-TYPE
	SYNTAX  Integer32
	UNITS	"0.1 degree Celsius"
	MAX-ACCESS read-only
	STATUS  current
	DESCRIPTION
		"actual temperature"
	-- 1.3.6.1.4.1.28507.62.1.6.1.1.2
	::= { pdu8311SensorEntry 2 }


pdu8311HygroSensor OBJECT-TYPE
	SYNTAX  Integer32
	UNITS	"0.1 percent humidity"
	MAX-ACCESS read-only
	STATUS  current
	DESCRIPTION
		"actual humidity"
	-- 1.3.6.1.4.1.28507.62.1.6.1.1.3
	::= { pdu8311SensorEntry 3 }


pdu8311InputSensor OBJECT-TYPE
	SYNTAX  INTEGER {
			off(0),
			on(1) }
	MAX-ACCESS read-only
	STATUS  current
	DESCRIPTION
		"logical state of input sensor"
	-- 1.3.6.1.4.1.28507.62.1.6.1.1.4
	::= { pdu8311SensorEntry 4 }


-- Conformance
--

pdu8311Conf OBJECT IDENTIFIER 
	-- 1.3.6.1.4.1.28507.62.2
	::= { gadsPDU8311 2 }

-- Groups
--

pdu8311Groups OBJECT IDENTIFIER 
	-- 1.3.6.1.4.1.28507.62.2.1
	::= { pdu8311Conf 1 }

-- Compliance
--

pdu8311Compls OBJECT IDENTIFIER 
	-- 1.3.6.1.4.1.28507.62.2.2
	::= { pdu8311Conf 2 }


pdu8311TempEvtSen NOTIFICATION-TYPE
	OBJECTS {
		pdu8311SensorIndex,
		pdu8311TempSensor}
	STATUS  current
	DESCRIPTION
		"temperature limits exceeded"
	-- 1.3.6.1.4.1.28507.62.3.1
	::= { events 1 }


pdu8311HygroEvtSen NOTIFICATION-TYPE
	OBJECTS {
		pdu8311SensorIndex,
		pdu8311HygroSensor}
	STATUS  current
	DESCRIPTION
		"hygro limits exceeded"
	-- 1.3.6.1.4.1.28507.62.3.2
	::= { events 2 }


pdu8311InputEvtSen NOTIFICATION-TYPE
	OBJECTS {
		pdu8311SensorIndex,
		pdu8311InputSensor}
	STATUS  current
	DESCRIPTION
		"change of logical input sensor state"
	-- 1.3.6.1.4.1.28507.62.3.3
	::= { events 3 }


pdu8311LineAmperageEvt NOTIFICATION-TYPE
	OBJECTS {
		pdu8311PowerIndex,
		pdu8311PowerActive,
		pdu8311Current,
		pdu8311Voltage,
		pdu8311Frequency,
		pdu8311PowerApparent,
		pdu8311PowerReactive}
	STATUS  current
	DESCRIPTION
		"Event is triggered when a measured
		current is crossing the entered limits"
	-- 1.3.6.1.4.1.28507.62.3.6
	::= { events 6 }

pdu8311BasicGroup OBJECT-GROUP
	OBJECTS {
		pdu8311TrapCtrl,
		pdu8311TrapIPIndex,
		pdu8311TrapAddr,
		pdu8311ActivePowerChan,
		pdu8311PowerIndex,
		pdu8311ChanStatus,
		pdu8311AbsEnergyActive,
		pdu8311PowerActive,
		pdu8311Current,
		pdu8311Voltage,
		pdu8311Frequency,
		pdu8311PowerFactor,
		pdu8311Pangle,
		pdu8311PowerApparent,
		pdu8311PowerReactive,
		pdu8311AbsEnergyReactive,
		pdu8311AbsEnergyActiveResettable,
		pdu8311AbsEnergyReactiveResettable,
		pdu8311ResetTime,
		pdu8311ForwEnergyActive,
		pdu8311ForwEnergyReactive,
		pdu8311ForwEnergyActiveResettable,
		pdu8311ForwEnergyReactiveResettable,
		pdu8311RevEnergyActive,
		pdu8311RevEnergyReactive,
		pdu8311RevEnergyActiveResettable,
		pdu8311RevEnergyReactiveResettable,
		pdu8311ResidualCurrent,
		pdu8311SensorIndex,
		pdu8311TempSensor,
		pdu8311HygroSensor,
		pdu8311InputSensor,
		pdu8311AirPressure,
		pdu8311DewPoint,
		pdu8311DewPointDiff,
		pdu8311Buzzer,
		pdu8311ExtSensorName,
		pdu8311LineSensorName }
	STATUS  current
	DESCRIPTION
		"Basic objects."
	-- 1.3.6.1.4.1.28507.62.2.1.1
	::= { pdu8311Groups 1 }

pdu8311NotificationGroup NOTIFICATION-GROUP
	NOTIFICATIONS {
		pdu8311TempEvtSen,
		pdu8311HygroEvtSen,
		pdu8311InputEvtSen,
		pdu8311LineAmperageEvt,
		pdu8311AirPressureEvtSen,
		pdu8311DewPtDiffEvtSen,
		pdu8311LineResidualCurrentEvt }
	STATUS  current
	DESCRIPTION ""
	-- 1.3.6.1.4.1.28507.62.2.1.2
	::= { pdu8311Groups 2 }

pdu8311AirPressure OBJECT-TYPE
	SYNTAX  Integer32
	UNITS	"1 hPA (hectopascal) ~ 1 milibar"
	MAX-ACCESS read-only
	STATUS  current
	DESCRIPTION
		"actual air pressure"
	-- 1.3.6.1.4.1.28507.62.1.6.1.1.5
	::= { pdu8311SensorEntry 5 }


pdu8311DewPoint OBJECT-TYPE
	SYNTAX  Integer32
	UNITS	"0.1 degree Celsius"
	MAX-ACCESS read-only
	STATUS  current
	DESCRIPTION
		"dew point for actual temperature and humidity"
	-- 1.3.6.1.4.1.28507.62.1.6.1.1.6
	::= { pdu8311SensorEntry 6 }


pdu8311DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.62.1.6.1.1.7
	::= { pdu8311SensorEntry 7 }


pdu8311Buzzer OBJECT-TYPE
	SYNTAX  Integer32 (0..1)
	UNITS	"0 = Off, 1 = On"
	MAX-ACCESS read-write
	STATUS  current
	DESCRIPTION
		"turn Buzzer on and off"
	-- 1.3.6.1.4.1.28507.62.1.3.10
	::= { pdu8311IntActors 10 }



pdu8311LineResidualCurrentEvt NOTIFICATION-TYPE
	OBJECTS {
		pdu8311PowerIndex,
		pdu8311PowerActive,
		pdu8311Current,
		pdu8311ResidualCurrent,
		pdu8311Voltage,
		pdu8311Frequency,
		pdu8311PowerApparent,
		pdu8311PowerReactive}
	STATUS  current
	DESCRIPTION
		"Event is triggered when a measured
		residual current is crossing the entered limits"
	-- 1.3.6.1.4.1.28507.62.3.7
	::= { events 7 }

END
